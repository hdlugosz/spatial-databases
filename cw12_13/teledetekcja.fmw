FME workspace teledetekcja.fmw
Startup Python:
      import smtplib
      from socket import gaierror
      import fmeobjects
      import fme
      from datetime import datetime

      port = 2525
      smtp_server = "smtp.mailtrap.io"
      login = "5096121fb3a229" # your login generated by Mailtrap
      password = "ef104308c18029" # your password generated by Mailtrap

      mail = fme.macroValues['CUSTOMER_EMAIL']
      district = fme.macroValues['DISTRICT']
      time =  datetime.now().strftime("%H:%M:%S %d/%m/%Y")

      # specify the sender’s and receiver’s email addresses
      sender = fme.macroValues['EMAIL']
      receiver = mail
      # type your message: use two newlines (\n) to separate the subject from the message body, and use 'f' to  automatically insert variables in the text
      message = f"""\
      Subject: Hi Mailtrap
      To: {receiver}
      From: {sender}

      Drogi uzytkowniku {mail}, o godzinie {time}
      rozpoczeto przetwarzanie danych dla {district}."""

      try:
          #send your message with credentials specified above
          with smtplib.SMTP(smtp_server, port) as server:
              server.login(login, password)
              server.sendmail(sender, receiver, message)

          # tell the script to report if your message was sent or which errors need to be fixed
          print('Sent')
      except (gaierror, ConnectionRefusedError):
          print('Failed to connect to the server. Bad connection settings?')
      except smtplib.SMTPServerDisconnected:
          print('Failed to connect to the server. Wrong user/password?')
      except smtplib.SMTPException as e:
          print('SMTP error occurred: ' + str(e))
Shutdown Python:
      import smtplib
      from socket import gaierror
      import fmeobjects
      import fme
      from datetime import datetime
      from email.mime.text import MIMEText
      from email.mime.image import MIMEImage
      from email.mime.multipart import MIMEMultipart
      import os

      port = 2525
      smtp_server = "smtp.mailtrap.io"
      login = "5096121fb3a229" # your login generated by Mailtrap
      password = "ef104308c18029" # your password generated by Mailtrap

      mail = fme.macroValues['CUSTOMER_EMAIL']
      district = fme.macroValues['DISTRICT']
      time =  datetime.now().strftime("%H:%M:%S %d/%m/%Y")

      # specify the sender’s and receiver’s email addresses
      sender = fme.macroValues['EMAIL']
      receiver = mail
      # type your message: use two newlines (\n) to separate the subject from the message body, and use 'f' to  automatically insert variables in the text
      message = f"""\
      To: {receiver}
      From: {sender}

      Drogi uzytkowniku {mail}, skrypt wykonywal sie x czasu.
      Statystyki pliku tiff:
          Odchylenie: {stdev}
          Srednia: {mean}

      Mail zawiera zalacznik."""

      email = MIMEMultipart()
      email['Subject'] = "Statystyki"
      email['From'] = sender
      email['To'] = receiver

      txt = MIMEText(message)
      email.attach(txt)

      with open("F:/HUBERT/GEOINFORMATYKA/V semestr/Bazy Danych Przestrzennych/cw12_13/Powiaty.tif", 'rb') as f:
          img = f.read()

      att = MIMEImage(img, name=os.path.basename("F:/HUBERT/GEOINFORMATYKA/V semestr/Bazy Danych Przestrzennych/cw12_13/Powiaty.tif"))
      email.attach(att)

      try:
          #send your message with credentials specified above
          with smtplib.SMTP(smtp_server, port) as server:
              server.login(login, password)
              server.sendmail(sender, receiver, email.as_string())

          # tell the script to report if your message was sent or which errors need to be fixed
          print('Sent')
      except (gaierror, ConnectionRefusedError):
          print('Failed to connect to the server. Bad connection settings?')
      except smtplib.SMTPServerDisconnected:
          print('Failed to connect to the server. Wrong user/password?')
      except smtplib.SMTPException as e:
          print('SMTP error occurred: ' + str(e))

Parameters:
- CLOUDS =
- CUSTOMER_EMAIL =
- DISTRICT =
- DestDataset_TIFF =
- EMAIL =
- END_DATE =
- PASSWORD =
- START_DATE =
- SourceDataset_SHAPEFILE =

Readers:
- SHAPEFILE_1: SHAPEFILE from $(SourceDataset_SHAPEFILE)

Writers:
- TIFF_1: TIFF to $(DestDataset_TIFF)

Powiaty (reader SHAPEFILE_1)
    attributes: JPT_SJR_KO varchar(3), JPT_KOD_JE varchar(20), JPT_NAZWA_ varchar(128), JPT_ORGAN_ varchar(254), JPT_JOR_ID long, WERSJA_OD date, WERSJA_DO date, WAZNY_OD date, WAZNY_DO date, JPT_KOD__1 varchar(3), JPT_NAZWA1 varchar(3), JPT_ORGAN1 varchar(3), JPT_WAZNA_ varchar(3), ID_BUFORA_ double, ID_BUFORA1 double, ID_TECHNIC long, IIP_PRZEST varchar(20), IIP_IDENTY varchar(128), IIP_WERSJA varchar(32), JPT_KJ_IIP varchar(20), JPT_KJ_I_1 varchar(128), JPT_KJ_I_2 varchar(32), JPT_OPIS varchar(254), JPT_SPS_KO varchar(3), ID_BUFOR_1 long, JPT_ID long, JPT_KJ_I_3 varchar(3), Shape_Leng double, Shape_Area double
    -> Reprojector
Reprojector
    DEST = LL84
    INTERPOLATION_TYPE_NAME = Nearest Neighbor
    RASTER_CELL_SIZE = Preserve Cells
    RASTER_TOLERANCE = 0.0
    REPROJECTED -> Tester
Tester
    BOOL_OP = OR
    COMPOSITE_TEST = 1
    TEST_CLAUSE = CASE_INSENSITIVE_TEST @Value(JPT_NAZWA_) CONTAINS $(DISTRICT)
    TEST_MODE = TEST
    PASSED -> SentinelDownloader [Initiator]
    PASSED -> Clipper [CLIPPER]
SentinelDownloader
    BEGIN = $(START_DATE)
    Band_Resolution = 60m
    CloudCover = $(CLOUDS)
    END = $(END_DATE)
    LEVEL = Level 2A
    key_name = hdlugosz
    key_pw =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
    platform = Sentinel-2
    zip_output = $(FME_MF_DIR)data.zip
    Band_4 -> Sampler
    Band_4 -> NoFeaturesTester
    Band_8A -> Sampler_2
Sampler
    RATE = 1
    SAMPLE_MODE = No
    SAMPLE_TYPE_LONG = First N Features
    SAMPLED -> NDVICalculator [Red]
Sampler_2
    RATE = 1
    SAMPLE_MODE = No
    SAMPLE_TYPE_LONG = First N Features
    SAMPLED -> NDVICalculator [Infrared]
NDVICalculator
    COLORIZE = Blue-Yellow-Green Palette
    INDEXTYPE = NDVI
    SAVIADJUSTMENT = 0.5
    -> Reprojector_2
Reprojector_2
    DEST = LL84
    INTERPOLATION_TYPE_NAME = Nearest Neighbor
    RASTER_CELL_SIZE = Preserve Cells
    RASTER_TOLERANCE = 0.0
    REPROJECTED -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> RasterStatisticsCalculator
    INSIDE -> Powiaty (writer TIFF_1)
Powiaty (writer TIFF_1)
    attributes: JPT_SJR_KO char(3), JPT_KOD_JE char(20), JPT_NAZWA_ char(128), JPT_ORGAN_ char(254), JPT_JOR_ID integer, WERSJA_OD date, WERSJA_DO date, WAZNY_OD date, WAZNY_DO date, JPT_KOD__1 char(3), JPT_NAZWA1 char(3), JPT_ORGAN1 char(3), JPT_WAZNA_ char(3), ID_BUFORA_ float, ID_BUFORA1 float, ID_TECHNIC integer, IIP_PRZEST char(20), IIP_IDENTY char(128), IIP_WERSJA char(32), JPT_KJ_IIP char(20), JPT_KJ_I_1 char(128), JPT_KJ_I_2 char(32), JPT_OPIS char(254), JPT_SPS_KO char(3), ID_BUFOR_1 integer, JPT_ID integer, JPT_KJ_I_3 char(3), Shape_Leng float, Shape_Area float
RasterStatisticsCalculator
    RASTER_LEVEL = BAND_ONLY
    RASTER_STATS = "0   MEAN   STDEV  "
    -> PythonCaller
PythonCaller
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              FME_MacroValues['mean'] = feature.getAttribute('band0.mean')
              FME_MacroValues['stdev'] = feature.getAttribute('band0.stdev')

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
NoFeaturesTester
    NOINPUT -> Emailer
Emailer
    ATTACHMENTTABLE = F:\HUBERT\GEOINFORMATYKA\V semestr\Bazy Danych Przestrzennych\cw12_13\logs.log  autodetect
    BODY:
      Nie znaleziono zobrazowania dla podanych parametrów:
      powiat: $(DISTRICT)
      data początkowa: $(START_DATE)
      data końcowa: $(END_DATE)
      maksymalne zachmurzenie: $(CLOUDS)
    FROM = $(EMAIL)
    SERVICE = Generic SMTP
    SMTP_CONNECTION = HOST;smtp.mailtrap.io;PORT;2525;ENCRYPTION;None;TIMEOUT;60;AUTHENTICATION;YES;USERNAME;5096121fb3a229;PASSWORD;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;FME_CONTROLLER_QUERY_FILE;dependencies/Generic SMTP.fme;FME_CONTROLLER_CHOICE;Generic SMTP
    SUBJECT = Nie znaleziono zobrazowania dla podanych parametrów
    TO = $(CUSTOMER_EMAIL)
    Sent -> Terminator
Terminator
    MESSAGE = Translation Terminated

FME custom transformer ZipExtractor
Extracts files archived in a zip file, and then outputs features for every extracted file and directory.
    Each resulting feature has two attributes storing full path string of an extracted file/directory - 
    "path_unix"
    (UNIX style) and 
    "path_windows"
    (Windows style), and also has an attribute that indicates the depth of the file/directory in the extracted directory hierarchy - 
    "path_depth" 
    (integer starting from 1).
    The features containing file path will be output through the File port, and the features containing directory path will be output through the Directory port. 
    All the extracted files will be saved into a subfolder under the folder specified with the "Destination Root Folder" parameter. The subfolder name will be the same as the source zip file name without extension. For example, if the source zip file name is 
    "data.zip"
    and the specified root folder path is 
    "C:\root"
    , extracted files will be saved into 
    "C:\root\data"
    .
    If the same name folder exists under the specified root folder, a number will be added to the destination subfolder name as suffix to differentiate from the existing folder, by default. e.g. 
    "C:\root\data_1"
    , 
    "C:\root\data_2"
    , and so on. 
    If you set "Yes" to the "Replace Existing Destination Subfolder" parameter, the existing subfolder and all files within it will be removed, and then the destination subfolder will be created newly.
    By default, this transformer will NOT unzip zip files that are archived (nested) in the source zip file. If you set "Yes" to the "Unzip Nested Zip Files Recursively" parameter, this transformer unzips all the nested zip files recursively.
    All attributes of the input feature will be propagated to the output features, but the geometry and coordinate system will not be preserved.
    If the specified source zip file or destination root folder is invalid, the input feature will be output through the <Rejected> port.
    Note: The Unzipper (FME Hub) can also be used to unzip a zip file. The ZipExtractor may be useful if you need to specify the destination root folder and/or to unzip nested zip file(s).
Parameters
    Source Zip File
    :
    Specify a zip file that should be extracted. The zip file name has to end with the extension ".zip" (case insensitive) by default, but optionally, you can also specify any extension(s) which this transformer should attempt to extract as a zip file. See the Allowable Source/Nested Zip File Extensions parameter.
    Destination Root Folder
    :
    Specify a folder in which a subfolder containing all extracted files should be created. If you leave this parameter blank, this transformer treats the folder containing the source zip file as the destination root folder.
    All the extracted files will be saved into a subfolder under the root folder. The subfolder name will be the same as the source zip file name without extension. For example, if the source zip file name is 
    "data.zip"
    and the specified root folder path is 
    "C:\root"
    , extracted files will be saved into 
    "C:\root\data"
    .
    Replace Existing Destination Subfolder
    :
    By default, a number will be added to the destination subfolder name as suffix if the same name folder exists under the spcified root folder. e.g. 
    "C:\root\data_1"
    , 
    "C:\root\data_2"
    , and so on. If you set "Yes" to this parameter, the existing subfolder and all files within it will be removed, and then the destination subfolder will be created newly. 
    Unzip Nested Zip Files Recursively
    :
    By default, this transformer will NOT unzip zip files that are archived (nested) in the source zip file. If you set "Yes" to this parameter, this transformer unzips all the nested zip files recursively.
    Preserve Nested Zip Files
    :
    By default, zip files nested in the source zip file will be removed after unzipping them, when the "Unzip Nested Zip Files Recursively" parameter is set to "Yes". If you set "Yes" to this parameter, the nested zip files will also be preserved.
    This parameter affects the result only when the "Unzip Nested Zip Files Recursively" parameter is set to "Yes". When the "Unzip Nested Zip Files Recursively" is set to "No", nested zip files always will be preserved regardless of this parameter.
    Allowable Source/Nested Zip File Extension(s)
    :
    By default, this transformer accepts only zip files whose name end with the extension ".zip" (case insensitive). However, if you want to extract zip files with other extension, you can specify allowable extention(s) via these parameters, with space-separated format when specifying two or more.
    Here, "Source Zip File" means that the top level zip file which would be set to the Source Zip File parameter; "Nested Zip File"means that internal zip file(s) which have been archived within the source zip file.
    If you leave the parameter field blank (it's the default), only ".zip" (case insensitive) will be allowable as zip file extension.
    Note that "zip" won't be allowable if you have set one or more extension other than ".zip" to the parameter. If you want to allow ".zip" and other extension(s) simultaneously, specify all possible extensions including ".zip" with the parameter.
    The leading dot "." of extensions can be omitted.

Parameters:
- EXT_N =
- EXT_S =
- PRESERVE =
- RECURSIVE =
- REPLACE =
- ROOT_FOLDER =
- ZIP_PATH =

Input (input)
    -> ParameterFetcher
ParameterFetcher
    ATTR_LIST = __unzipper.zip_path {$(ZIP_PATH)} __unzipper.root_folder {$(ROOT_FOLDER)} __unzipper.replace {$(REPLACE)} __unzipper.recursive {$(RECURSIVE)} __unzipper.preserve {$(PRESERVE)} __unzipper.ext_s {$(EXT_S)} __unzipper.ext_n {$(EXT_N)}
    -> PythonCaller
PythonCaller
    HIDE_ATTRIBUTES = __unzipper.ext_n __unzipper.ext_s __unzipper.preserve __unzipper.recursive __unzipper.replace __unzipper.root_folder __unzipper.zip_path
    NEW_ATTRIBUTES = path_unix path_windows path_depth __unzipper.flag _error_message
    PYTHONSOURCE:
      # 2018-06-14,  Takashi Iijima,  Added Allowable Source/Nested Zip File Extention(s) parameter.
      # 2016-01-25,  Takashi Iijima,  Updated to trim leading and trailing whitespaces of specified path strings.
      # 2016-01-23,  Takashi Iijima,  Updated:
      # - added function to check file extension to prevent extracting non-archiver zip files. e.g. Excel (*.xlsx) etc.
      # - added codes to create desitnation root folder if it is specified but doesn't exist.
      # - added option to preserve nested zip files after unzipping them.
      # - added "path_depth" attribute to output features.
      # 2016-01-21,  Takashi Iijima,  Original Implementation

      import fmeobjects, zipfile, os

      class ZipExtractor(object):
          def __init__(self):
              self.logger = fmeobjects.FMELogFile()
              self.kFlagFile = 'file'
              self.kFlagDirectory = 'directory'
              self.kFlagReject = 'reject'
              self.kFlagTerminate = 'terminate'
              self.zipExtS = set(['.zip'])
              self.zipExtN = set(['.zip'])

          def isZipFileS(self, path):
              _, ext = os.path.splitext(path)
              return ext.lower() in self.zipExtS and zipfile.is_zipfile(path)

          def isZipFileN(self, path):
              _, ext = os.path.splitext(path)
              return ext.lower() in self.zipExtN and zipfile.is_zipfile(path)

          def input(self, feature):
              # Retrieve parameter values from feature attributes, then remove the attributes.
              # Zip path may end with a path separator if extracted by the FilenamePartExtractor as "_dirpath".
              zipPath = feature.getAttribute('__unzipper.zip_path').strip().rstrip('\\/')
              rootFolder = feature.getAttribute('__unzipper.root_folder').strip()
              replace = (feature.getAttribute('__unzipper.replace') == 'Yes')
              self.recursive = (feature.getAttribute('__unzipper.recursive') == 'Yes')
              self.preserve = (feature.getAttribute('__unzipper.preserve') == 'Yes')
              extS = set(feature.getAttribute('__unzipper.ext_s').split())
              extN = set(feature.getAttribute('__unzipper.ext_n').split())
              feature.removeAttrsWithPrefix('__unzipper.')

              if extS:
                  self.zipExtS = set([(e if e.startswith('.') else ('.%s' % e)).lower() for e in extS])
              if extN:
                  self.zipExtN = set([(e if e.startswith('.') else ('.%s' % e)).lower() for e in extN])

              # If destination root folder is specified but doesn't exist, try creating the directory.
              isRootValid = True
              if rootFolder and not os.path.exists(rootFolder):
                  try:
                      os.makedirs(rootFolder)
                  except:
                      isRootValid = False

              # If specified zip file or destination root folder is invalid, reject the input feature.
              if not os.path.exists(zipPath) or not self.isZipFileS(zipPath) or not isRootValid:
                  self.logger.logMessageString('Specified zip file or destination root folder is invalid.',  \
                      fmeobjects.FME_WARN)
                  feature.setAttribute('__unzipper.flag', self.kFlagReject)
                  self.pyoutput(feature)
                  return

              # Define destination folder path: <root folder>/<source zip file name without extension>
              # If root folder is not specified, treat the folder containing source zip file as root folder.
              zipPath = os.path.abspath(zipPath)
              zipFolder, zipName = os.path.split(zipPath)
              destFolder = os.path.join(os.path.abspath(rootFolder) if rootFolder else zipFolder, zipName[:-4])

              try:
                  # If the destination folder exists,
                  # - remove the existing folder and all files within it when REPLACE is set to Yes,
                  # - add suffix to the folder path when REPLACE is set to No.
                  if os.path.exists(destFolder):
                      if replace:
                          for dirpath, dirs, files in os.walk(destFolder, topdown=False):
                              for name in files:
                                  os.remove(os.path.join(dirpath, name))
                              for name in dirs:
                                  os.rmdir(os.path.join(dirpath, name))
                          os.rmdir(destFolder)
                      else:
                          format, n = '%s_%d', 1
                          while os.path.exists(format % (destFolder, n)): n += 1
                          destFolder = format % (destFolder, n)

                  # Extract the zip file and output features containing extracted file/directory path.
                  self.pathInfos = [] # tuples list - (file or directory path, flag: 'file' or 'directory', depth)
                  self.extract(zipPath, destFolder, 1)
                  for path, flag, depth in self.pathInfos:
                      feat = feature.cloneAttributes()
                      feat.setAttribute('path_unix', path.replace('\\', '/'))
                      feat.setAttribute('path_windows', path.replace('/', '\\'))
                      feat.setAttribute('path_depth', depth)
                      feat.setAttribute('__unzipper.flag', flag)
                      self.pyoutput(feat)

              except Exception as ex:
                  feature.setAttribute('_error_message', 'Unexpected error: %s' % ex)
                  feature.setAttribute('__unzipper.flag', self.kFlagTerminate)
                  self.pyoutput(feature)

          # Extract a zip file.
          def extract(self, zipPath, destPath, depth):
              with zipfile.ZipFile(zipPath) as z: z.extractall(destPath)
              self.findFiles(destPath, depth)

          # Find and collect extracted file/directory paths.
          def findFiles(self, dirPath, depth):
              self.pathInfos.append((dirPath, self.kFlagDirectory, depth))
              depth += 1
              for fname in os.listdir(dirPath):
                  path = os.path.join(dirPath, fname)
                  if os.path.isdir(path):
                      self.findFiles(path, depth)
                  elif self.recursive and self.isZipFileN(path):
                      if self.preserve:
                          self.pathInfos.append((path, self.kFlagFile, depth))
                          self.extract(path, os.path.join(dirPath, fname[:-4]), depth)
                      else:
                          self.extract(path, os.path.join(dirPath, fname[:-4]), depth)
                          os.remove(path)
                  else:
                      self.pathInfos.append((path, self.kFlagFile, depth))
    PYTHONSYMBOL = ZipExtractor
    -> AttributeFilter
AttributeFilter
    ATTR_NAME = __unzipper.flag
    ATTR_VALUES = file,directory,reject,terminate,<EMPTY>,<MISSING>,<NULL>,<UNFILTERED>
    file -> File (output)
    directory -> Directory (output)
    reject -> <Rejected> (output)
    terminate -> AttributeRemover
File (output)
Directory (output)
<Rejected> (output)
AttributeRemover
    REMOVE_ATTRS = __unzipper.flag,path_depth,path_unix,path_windows
    -> Terminator
Terminator
    MESSAGE = @Value(_error_message)

FME custom transformer SentinelDownloader
Description 
This transformer allows you to access the COPERNICUS Open Access Hub and download Sentinel-II images right from the source.
Since the existing Sentinel-II reader targets an "Requester pays" Amazon bucket, AWS credentials are required in addition to a charge per x requests or GB.
Using the con terra SentinelDownloader transformer, you only need a free account from COPERNICUS Open Access Hub to access the Sentinel-II data.  
If you have any question or if you are looking for professional services support, please contact fme@conterra.de. 
Configuration 
Input Port 
Initiator: 
An Area Of Interest (AOI) polygon feature OR 
A point feature (e.g. defined in the Creator transformer) OR 
A (textual) WKT representation of a point or polygon feature (e.g. POINT(7.6528 51.9352) )
Coordinates must be in LL84. 
Parameters/Properties 
KEY_NAME:
Please enter your user name from the COPERNICUS Open Access Hub 
KEY_ PW: 
Please enter your account password from the COPERNICUS Open Access Hub 
BEGIN [optional]: 
Choose the start date of your ingestion period 
END [optional]: 
Choose the end date of your ingestion period 
LEVEL: 
Choose between the two data product levels: Level 1C (Top of atmosphere reflectances, geometric and radiometric corrected) and Level 2A (Botton of atmosphere reflectances)
CLOUDCOVER [optional]: 
In this optional parameter, you can choose whether you want your results are filtered by a maximum cloud cover percentage. Keep in mind that this parameter could be the bottleneck of your search query as it possibly will exclude data if the parameter value is too small. 
BAND_RESOLUTION: 
Choose between the three possible spatial resolutions (ground sampling distance) 10m, 20m, 60m, and All. 
ZIP_OUTPUT: 
Set a location where the downloaded zip file is saved. Please regard to type in the ".zip" file format at the end of the folder name.
Output Ports 
The output depends on the choosen product Level and spatial resolution. For detailed information about a specific band, see this. 
Despite the choosen spatial resolution, the whole image stack (Level1C ~0.8GB / Level 2A ~1GB) will be downloaded from the COPERNICUS Open Access Hub and stored in the ZIP_OUTPUT destination folder. Users should consider deleting unnecessary data afterwards. 
Level 1C: 
10m 
Bands 2, 3, 4, and 8. 
20m 
Bands 5, 6, 7, 8A, 11, and 12. 
60m 
Bands 1, 9, and 10 
All 
All 13 bands at their best posible spatial resolution (see above) and the True Color Image (TCI) 
Level 2A: 
10m 
Bands 2, 3, 4, and 8. 
20m
Bands 2, 3, 4, 5, 6, 7, 8A, 11, and 12 (all bands in 20m spatial resolution) 
60m 
Bands 1, 2, 3, 4, 5, 6, 7, 8A, 9, 11, and 12 (all bands in 60m spatial resolution) 
All 
All 12 bands at their best posible spatial resolution (see above) and the True Color Image (TCI)

Parameters:
- BEGIN =
- Band_Resolution =
- CloudCover =
- END =
- FME_USER_PARAM_PRIVATE_GRP =
- LEVEL =
- key_name =
- key_pw =
- platform =
- zip_output =

Initiator (input)
    -> TextEncoder
Note: Generate API-Key from name:pw and Base64 encoding
Note: Placeholder S1
TextEncoder
    DEST_ATTR = _key_encoded
    ENCODING_TYPE = BASE64_ENCODE
    STRING_TO_ENCODE = $(key_name):$(key_pw)
    -> VariableSetter
VariableSetter
    SCOPE = Global
    VALUE = @Value(_key_encoded)
    VARNAME = key
    -> GeometryFilter
XMLFragmenter
    ATTRIBUTE_XML = _response_body
    EMBEDDED_EXPRESSIONS = entry
    FEATURE_TYPES_FORMAT_NAME = XML
    MERGE_ATTRS = No
    REJECT_FEATURES_WITH_NO_FRAGMENTS = YES
    XML_SOURCE_TYPE = Attribute with XML document
    FRAGMENTS -> Tester_2
    <REJECTED> -> Terminator_2
Band_1 (output)
Band_2 (output)
Band_3 (output)
Band_4 (output)
Band_5 (output)
Band_6 (output)
Band_7 (output)
Band_8 (output)
Band_8A (output)
Band_9 (output)
Band_10 (output)
Band_11 (output)
Band_12 (output)
TCI (output)
Note: Terminate the translation if no results were acquired
Terminator_2
    MESSAGE:
      Translation Terminated. There are zero search results with your parameters.
      To get results, please change the parameters, e.g. the ingestion date or the maximum cloud coverage percentage.

Bookmark: Downloading Sentinel-2 data
GeometryFilter
    BREAK_AGG = No
    GEOM_PORT_NAMES = Point Area Text
    POINT -> Reprojector
    AREA -> BoundingBoxReplacer
    TEXT -> AttributeCreator_3
    <UNFILTERED> -> Terminator
Note: Terminate the translation if an unexpected input exists
Terminator
    MESSAGE = Translation Terminated because none of the input parameters was either a point, polygon, or text (WKT) feature.

Bookmark: Spatial filter by point object
Reprojector
    DEST = LL-WGS84
    INTERPOLATION_TYPE_NAME = Nearest Neighbor
    RASTER_CELL_SIZE = Preserve Cells
    RASTER_TOLERANCE = 0.0
    SOURCE = Read from feature
    REPROJECTED -> CoordinateExtractor
CoordinateExtractor
    IND = 0
    MODE = Specify Coordinate
    X_ATTR = _x
    Y_ATTR = _y
    Z_ATTR = _z
    -> AttributeCreator
AttributeCreator
    ATTR_TABLE:
      SET_TO date_param = ingestionDate:[@DateTimeFormat($(BEGIN),%Y-%m-%d)T00:00:00.000Z TO @DateTimeFormat($(END),%Y-%m-%d)T23:59:00.000Z]
      SET_TO product_type = FME_CONDITIONAL:DEFAULT_VALUE'producttype:S2MSI2A'BOOL_OP;OR;COMPOSITE_TEST;<Unused>;TEST $(LEVEL) = Level 1C'producttype:S2MSI1C'FME_NUM_CONDITIONS2___
    -> HTTPCaller_3
Note: Select based on intersection with Point and platformname:Sentinel-2 and ingestion date
HTTPCaller_3
    CONNECTION_TIMEOUT_LENGTH = 60
    CUSTOM_HEADERS = Authorization;Basic @Value(_key_encoded)
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://scihub.copernicus.eu/dhus/search?q=(footprint:"Intersects(@Value(_x) @Value(_y))" AND platformname:$(platform) AND @Value(product_type) AND @Value(date_param) AND cloudcoverpercentage:[0 TO $(CloudCover)])
    TRANSFER_TIMEOUT_LENGTH = 90
    USE_COOKIES = No
    VERIFY_SSL_CERTIFICATES = Yes
    -> XMLFragmenter

Bookmark: Spatial filter by Polygon object
BoundingBoxReplacer
    BOXTYPE = 2D Bounding Box
    BOX -> CoordinateExtractor_2
CoordinateExtractor_2
    LIST_NAME = coord
    MODE = All Coordinates
    -> AttributeCreator_2
AttributeCreator_2
    ATTR_TABLE:
      SET_TO date_param = ingestionDate:[@DateTimeFormat($(BEGIN),%Y-%m-%d)T00:00:00.000Z TO @DateTimeFormat($(END),%Y-%m-%d)T23:59:00.000Z]
      SET_TO poly = POLYGON((@Value(coord{0}.x) @Value(coord{0}.y),@Value(coord{1}.x) @Value(coord{1}.y),@Value(coord{2}.x) @Value(coord{2}.y),@Value(coord{3}.x) @Value(coord{3}.y),@Value(coord{4}.x) @Value(coord{4}.y)))
      SET_TO product_type = FME_CONDITIONAL:DEFAULT_VALUE'producttype:S2MSI2A'BOOL_OP;OR;COMPOSITE_TEST;<Unused>;TEST $(LEVEL) = Level 1C'producttype:S2MSI1C'FME_NUM_CONDITIONS2___
    -> HTTPCaller
Note: Select based on intersection with Polygon and platformname:Sentinel-2 and ingestion date
HTTPCaller
    CONNECTION_TIMEOUT_LENGTH = 60
    CUSTOM_HEADERS = Authorization;Basic @Value(_key_encoded)
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://scihub.copernicus.eu/dhus/search?q=(footprint:"Intersects(@Value(poly))" AND platformname:$(platform)  AND @Value(product_type) AND @Value(date_param) AND cloudcoverpercentage:[0 TO $(CloudCover)])
    TRANSFER_TIMEOUT_LENGTH = 90
    USE_COOKIES = No
    VERIFY_SSL_CERTIFICATES = Yes
    -> XMLFragmenter

Bookmark: Spatial filter by Cordinates as Text
AttributeCreator_3
    ATTR_TABLE:
      SET_TO date_param = ingestionDate:[@DateTimeFormat($(BEGIN),%Y-%m-%d)T00:00:00.000Z TO @DateTimeFormat($(END),%Y-%m-%d)T23:59:00.000Z]
      SET_TO wkt_object = @Value(fme_text_string)
      SET_TO product_type = FME_CONDITIONAL:DEFAULT_VALUE'producttype:S2MSI2A'BOOL_OP;OR;COMPOSITE_TEST;<Unused>;TEST $(LEVEL) = Level 1C'producttype:S2MSI1C'FME_NUM_CONDITIONS2___
    -> TestFilter
TestFilter
    DEFAULT_VALUE = <UNFILTERED>
    TEST_LIST = "BOOL_OP,OR,COMPOSITE_TEST,""""""<Unused>"""""",TEST_CLAUSE,CASE_INSENSITIVE_TEST @Value(wkt_object) CONTAINS POINT",Point,"BOOL_OP,OR,COMPOSITE_TEST,""""""<Unused>"""""",TEST_CLAUSE,CASE_INSENSITIVE_TEST @Value(wkt_object) CONTAINS POLYGON",Polygon
    Point -> StringReplacer
    Polygon -> HTTPCaller_5
Note: Select based on intersection with WKT object and platformname:Sentinel-2 and ingestion date
HTTPCaller_5
    CONNECTION_TIMEOUT_LENGTH = 60
    CUSTOM_HEADERS = Authorization;Basic @Value(_key_encoded)
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://scihub.copernicus.eu/dhus/search?q=(footprint:"Intersects(@Value(wkt_object))" AND platformname:$(platform)  AND @Value(product_type) AND @Value(date_param) AND cloudcoverpercentage:[0 TO $(CloudCover)])
    TRANSFER_TIMEOUT_LENGTH = 90
    USE_COOKIES = No
    VERIFY_SSL_CERTIFICATES = Yes
    -> XMLFragmenter

Bookmark: POINT replacer
StringReplacer
    CASE = NO
    FIND_TEXT = POINT(
    NO_MATCH = _FME_NO_OP_
    REGEXP = NO
    SRC_ATTRS = wkt_object
    -> StringReplacer_2
StringReplacer_2
    CASE = NO
    FIND_TEXT = )
    NO_MATCH = _FME_NO_OP_
    REGEXP = NO
    SRC_ATTRS = wkt_object
    -> HTTPCaller_5

Bookmark: Filtering the level of imagery
Note: Product level?
Tester_2
    BOOL_OP = AND
    TEST_CLAUSE = TEST $(LEVEL) = Level 2A
    TEST_MODE = TEST
    PASSED -> Tester
    FAILED -> Tester_6
Note: Filter L2A data
Tester
    BOOL_OP = AND
    TEST_CLAUSE = CASE_INSENSITIVE_TEST @Value(xml_fragment) CONTAINS _MSIL2A_
    TEST_MODE = TEST
    PASSED -> XMLFragmenter_2
    PASSED -> XMLFlattener
    FAILED -> Logger_2
Logger_2
    LOG_FEATURE = NONE
    MAXFEATS = 20
    MESSAGE = Unfortunately, there is no L2A data availabe. Try to choose the option "Level 1C" at the "Product Level" parameter.
    SEVERITY = WARN
Note: Filter L1C data
Tester_6
    BOOL_OP = AND
    TEST_CLAUSE = CASE_INSENSITIVE_TEST @Value(xml_fragment) CONTAINS _MSIL1C_
    TEST_MODE = TEST
    PASSED -> XMLFlattener_2
    PASSED -> XMLFragmenter_2
    FAILED -> Logger_3
Logger_3
    LOG_FEATURE = NONE
    MAXFEATS = 20
    MESSAGE = Unfortunately, the search results do not match the search criteria.
    SEVERITY = WARN

Bookmark: Download L2A data
XMLFlattener
    ATTRIBUTE_XML = xml_fragment
    EMBEDDED_EXPRESSIONS = link
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = link.href
    XML_SOURCE_TYPE = Attribute with XML document
    -> VariableRetriever
VariableRetriever
    SCOPE = Global
    VALUE_ATTR = _keyAPI
    VARNAME = key
    -> HTTPCaller_2
Note: Download
HTTPCaller_2
    CONNECTION_TIMEOUT_LENGTH = 60
    CUSTOM_HEADERS = Authorization;Basic @Value(_keyAPI)
    ERROR_ATTR = _error
    FILE_PATH_ATTR = _response_file_path
    FOLLOW_REDIRECTS = Yes
    HTTP_METHOD = GET
    OUTPUT_FILENAME = $(zip_output)
    SAVE_FILE = File
    SAVE_MULTI = No
    STATUS_CODE_ATTR = _http_status_code
    TARGET_URL = @Value(link.href)
    TRANSFER_TIMEOUT_LENGTH = 90
    USE_COOKIES = No
    VERIFY_SSL_CERTIFICATES = Yes
    -> Junction

Bookmark: Write information to log file
XMLFragmenter_2
    ATTRIBUTE_XML = xml_fragment
    EMBEDDED_EXPRESSIONS = date[@name="ingestiondate"]
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = date
    REJECT_FEATURES_WITH_NO_FRAGMENTS = YES
    XML_SOURCE_TYPE = Attribute with XML document
    FRAGMENTS -> StatisticsCalculator
StatisticsCalculator
    COMPUTE_HISTOGRAM = NO
    COUNT_ATTR = _count
    PREPEND_ATTR_NAME_CHOICE = For multiple results only
    STATS_ATTRS = xml_matched_element
    SUMMARY -> FeatureMerger [REQUESTOR]
    COMPLETE -> ListBuilder
ListBuilder
    GROUPS_ORDERED = No
    LIST_ATTRS_TO_INCLUDE = date
    LIST_NAME = _datelist
    -> ListConcatenator
ListConcatenator
    DROP_EMPTY_PARTS = No
    LIST_ATTR = _datelist{}.date
    SEP = " & "
    VAL_ATTR = _concatenated
    -> FeatureMerger [SUPPLIER]
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = 1 1 AUTO
    MERGE_TYPE = Attributes Only
    PROCESS_DUPS = YES
    REJECT_NULL_MISSING_KEYS = No
    SUPPLIERS_FIRST = No
    MERGED -> Logger
Logger
    LOG_FEATURE = NONE
    MAXFEATS = 100
    MESSAGE:
      Your request delivers @Value(_count) result(s).
      The request delivers images at the following dates: @Value(_concatenated)
    SEVERITY = WARN

Bookmark: Download L1C data
XMLFlattener_2
    ATTRIBUTE_XML = xml_fragment
    EMBEDDED_EXPRESSIONS = link
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = link.href
    XML_SOURCE_TYPE = Attribute with XML document
    -> VariableRetriever_2
VariableRetriever_2
    SCOPE = Global
    VALUE_ATTR = _keyAPI
    VARNAME = key
    -> HTTPCaller_4
Note: Download
HTTPCaller_4
    CONNECTION_TIMEOUT_LENGTH = 60
    CUSTOM_HEADERS = Authorization;Basic @Value(_keyAPI)
    ERROR_ATTR = _error
    FILE_PATH_ATTR = _response_file_path
    FOLLOW_REDIRECTS = Yes
    HTTP_METHOD = GET
    OUTPUT_FILENAME = $(zip_output)
    SAVE_FILE = File
    SAVE_MULTI = No
    STATUS_CODE_ATTR = _http_status_code
    TARGET_URL = @Value(link.href)
    TRANSFER_TIMEOUT_LENGTH = 90
    USE_COOKIES = No
    VERIFY_SSL_CERTIFICATES = Yes
    -> Junction

Bookmark: Find the downloaded ZIP archive and unzip it
Junction
    -> FilenamePartExtractor
FilenamePartExtractor
    DIRPATH_ATTR = _dirpath
    SRC_ATTR = @Value(_response_file_path)
    -> ZipExtractor_2
Note: Unzip the downloaded file
ZipExtractor_2
    PRESERVE = No
    RECURSIVE = No
    REPLACE = No
    ROOT_FOLDER = @Value(_dirpath)
    ZIP_PATH = @Value(_response_file_path)
    File -> Tester_4
Note: Filter L2A data
Tester_4
    BOOL_OP = AND
    TEST_CLAUSE:
      CASE_INSENSITIVE_TEST @Value(xml_fragment) CONTAINS _MSIL2A_
      CASE_INSENSITIVE_TEST @Value(path_windows) CONTAINS GRANULE
    TEST_MODE = TEST
    PASSED -> Tester_3
    FAILED -> Tester_5

Bookmark: Split the unzipped images by resolution (Only L2A Product)
Tester_3
    BOOL_OP = OR
    TEST_CLAUSE:
      CASE_SENSITIVE_TEST @Value(path_windows) CONTAINS_REGEX B\d(\d|A)_\d\dm.jp2
      CASE_INSENSITIVE_TEST @Value(path_windows) CONTAINS TCI_10m
    TEST_MODE = TEST
    PASSED -> TestFilter_3
TestFilter_3
    DEFAULT_VALUE = <UNFILTERED>
    TEST_LIST:
      "BOOL_OP,COMPOSITE,COMPOSITE_TEST,""""""1 AND (2 OR 3) AND 4"""""",TEST_CLAUSE,CASE_INSENSITIVE_TEST @Value(path_windows) CONTAINS R10m
      TEST $(Band_Resolution) = 10m
      TEST $(Band_Resolution) = All
      CASE_INSENSITIVE_TEST @Value(path_windows) NOT_CONTAINS TCI_10m",10m,"BOOL_OP,COMPOSITE,COMPOSITE_TEST,""""""1 AND (2 OR (3 AND 4))"""""",TEST_CLAUSE,CASE_INSENSITIVE_TEST @Value(path_windows) CONTAINS R20m
      TEST $(Band_Resolution) = 20m
      TEST $(Band_Resolution) = All
      CASE_SENSITIVE_TEST @Value(path_windows) NOT_CONTAINS_REGEX _B(0[2348]|)_20m.jp2",20m,"BOOL_OP,COMPOSITE,COMPOSITE_TEST,""""""1 AND (2 OR (3 AND (4 AND 5 AND 6)))"""""",TEST_CLAUSE,CASE_INSENSITIVE_TEST @Value(path_windows) CONTAINS R60m
      TEST $(Band_Resolution) = 60m
      TEST $(Band_Resolution) = All
      CASE_SENSITIVE_TEST @Value(path_windows) NOT_CONTAINS_REGEX _B0(2|3|4|5|6|7)_60m.jp2
      CASE_SENSITIVE_TEST @Value(path_windows) NOT_CONTAINS_REGEX _B8A_60m.jp2
      CASE_SENSITIVE_TEST @Value(path_windows) NOT_CONTAINS_REGEX _B1(1|2)_60m.jp2",60m,"BOOL_OP,AND,COMPOSITE_TEST,""""""<Unused>"""""",TEST_CLAUSE,CASE_INSENSITIVE_TEST @Value(path_windows) CONTAINS_REGEX TCI_10m
      TEST $(Band_Resolution) = All",TCI
    10m -> FeatureReader_3 [INITIATOR]
    20m -> FeatureReader_3 [INITIATOR]
    60m -> FeatureReader_3 [INITIATOR]
    TCI -> FeatureReader_3 [INITIATOR]
FeatureReader_3
    ATTRIBUTES = JPEG2000,fme_basename
    ATTR_ACCUM_MODE = Only Use Result
    COMBINE_GEOM = Use Result
    DATASET = @Value(path_unix)
    FORMAT = JPEG2000
    INTERACT = <No Spatial Filter>
    JPEG2000_GROUP_BY_DATASET = No
    JPEG2000_JPEG2000_EXPOSE_FORMAT_ATTRS = fme_basename,char(50)
    JPEG2000_PREFER_FILE_CS_UNITS = Yes
    JPEG2000_READER_META_ATTRIBUTES = fme_dataset fme_basename
    JPEG2000_READ_OFFSETS_IN_CS_UNITS = No
    JPEG2000_USE_SEARCH_ENVELOPE = NO
    OUTPUT_FEATURES_DISPLAY = Schema and Data Features
    JPEG2000 -> TestFilter_4
TestFilter_4
    DEFAULT_VALUE = <UNFILTERED>
    TEST_LIST = "BOOL_OP,OR,COMPOSITE_TEST,""""""<Unused>"""""",TEST_CLAUSE,CASE_SENSITIVE_TEST @Value(fme_basename) CONTAINS_REGEX B01_\d\dm",B01,"BOOL_OP,OR,COMPOSITE_TEST,""""""<Unused>"""""",TEST_CLAUSE,CASE_SENSITIVE_TEST @Value(fme_basename) CONTAINS_REGEX B02_\d\dm",B02,"BOOL_OP,OR,COMPOSITE_TEST,""""""<Unused>"""""",TEST_CLAUSE,CASE_SENSITIVE_TEST @Value(fme_basename) CONTAINS_REGEX B03_\d\dm",B03,"BOOL_OP,OR,COMPOSITE_TEST,""""""<Unused>"""""",TEST_CLAUSE,CASE_SENSITIVE_TEST @Value(fme_basename) CONTAINS_REGEX B04_\d\dm",B04,"BOOL_OP,OR,COMPOSITE_TEST,""""""<Unused>"""""",TEST_CLAUSE,CASE_SENSITIVE_TEST @Value(fme_basename) CONTAINS_REGEX B05_\d\dm",B05,"BOOL_OP,OR,COMPOSITE_TEST,""""""<Unused>"""""",TEST_CLAUSE,CASE_SENSITIVE_TEST @Value(fme_basename) CONTAINS_REGEX B06_\d\dm",B06,"BOOL_OP,OR,COMPOSITE_TEST,""""""<Unused>"""""",TEST_CLAUSE,CASE_SENSITIVE_TEST @Value(fme_basename) CONTAINS_REGEX B07_\d\dm",B07,"BOOL_OP,OR,COMPOSITE_TEST,""""""<Unused>"""""",TEST_CLAUSE,CASE_SENSITIVE_TEST @Value(fme_basename) CONTAINS_REGEX B08_\d\dm",B08,"BOOL_OP,OR,COMPOSITE_TEST,""""""<Unused>"""""",TEST_CLAUSE,CASE_SENSITIVE_TEST @Value(fme_basename) CONTAINS_REGEX B8A_\d\dm",B8A,"BOOL_OP,OR,COMPOSITE_TEST,""""""<Unused>"""""",TEST_CLAUSE,CASE_SENSITIVE_TEST @Value(fme_basename) CONTAINS_REGEX B09_\d\dm",B09,"BOOL_OP,OR,COMPOSITE_TEST,""""""<Unused>"""""",TEST_CLAUSE,CASE_SENSITIVE_TEST @Value(fme_basename) CONTAINS_REGEX B10_\d\dm",B10,"BOOL_OP,OR,COMPOSITE_TEST,""""""<Unused>"""""",TEST_CLAUSE,CASE_SENSITIVE_TEST @Value(fme_basename) CONTAINS_REGEX B11_\d\dm",B11,"BOOL_OP,OR,COMPOSITE_TEST,""""""<Unused>"""""",TEST_CLAUSE,CASE_SENSITIVE_TEST @Value(fme_basename) CONTAINS_REGEX B12_\d\dm",B12,"BOOL_OP,OR,COMPOSITE_TEST,""""""<Unused>"""""",TEST_CLAUSE,CASE_SENSITIVE_TEST @Value(fme_basename) CONTAINS_REGEX TCI_10m",TCI
    B01 -> Band_1 (output)
    B02 -> Band_2 (output)
    B03 -> Band_3 (output)
    B04 -> Band_4 (output)
    B05 -> Band_5 (output)
    B06 -> Band_6 (output)
    B07 -> Band_7 (output)
    B08 -> Band_8 (output)
    B8A -> Band_8A (output)
    B09 -> Band_9 (output)
    B10 -> Band_10 (output)
    B11 -> Band_11 (output)
    B12 -> Band_12 (output)
    TCI -> TCI (output)

Bookmark: output the unzipped images band-wise (L1C Product)
Tester_5
    BOOL_OP = OR
    TEST_CLAUSE:
      CASE_SENSITIVE_TEST @Value(path_windows) CONTAINS_REGEX B\d(\d|A).jp2
      CASE_INSENSITIVE_TEST @Value(path_windows) CONTAINS TCI.jp2
    TEST_MODE = TEST
    PASSED -> TestFilter_6
TestFilter_6
    DEFAULT_VALUE = <UNFILTERED>
    TEST_LIST:
      "BOOL_OP,COMPOSITE,COMPOSITE_TEST,""""""1 AND (2 OR 3)"""""",TEST_CLAUSE,CASE_INSENSITIVE_TEST @Value(path_windows) CONTAINS_REGEX _B0[2348].jp2
      TEST $(Band_Resolution) = 10m
      TEST $(Band_Resolution) = All",10m,"BOOL_OP,COMPOSITE,COMPOSITE_TEST,""""""1 AND (2 OR (3 AND 4))"""""",TEST_CLAUSE,CASE_INSENSITIVE_TEST @Value(path_windows) CONTAINS_REGEX _B((0|8)([567]|A)|11|12).jp2
      TEST $(Band_Resolution) = 20m
      TEST $(Band_Resolution) = All
      CASE_SENSITIVE_TEST @Value(path_windows) NOT_CONTAINS_REGEX _B(0[2348]|).jp2",20m,"BOOL_OP,COMPOSITE,COMPOSITE_TEST,""""""1 AND (2 OR (3 AND (4 AND 5 AND 6)))"""""",TEST_CLAUSE,CASE_INSENSITIVE_TEST @Value(path_windows) CONTAINS_REGEX _B(0[19]|10).jp2
      TEST $(Band_Resolution) = 60m
      TEST $(Band_Resolution) = All
      CASE_SENSITIVE_TEST @Value(path_windows) NOT_CONTAINS_REGEX _B0(2|3|4|5|6|7).jp2
      CASE_SENSITIVE_TEST @Value(path_windows) NOT_CONTAINS_REGEX _B8A.jp2
      CASE_SENSITIVE_TEST @Value(path_windows) NOT_CONTAINS_REGEX _B1(1|2).jp2",60m,"BOOL_OP,AND,COMPOSITE_TEST,""""""<Unused>"""""",TEST_CLAUSE,CASE_INSENSITIVE_TEST @Value(path_windows) CONTAINS_REGEX TCI
      TEST $(Band_Resolution) = All",TCI
    10m -> FeatureReader_2 [INITIATOR]
    20m -> FeatureReader_2 [INITIATOR]
    60m -> FeatureReader_2 [INITIATOR]
    TCI -> FeatureReader_2 [INITIATOR]
FeatureReader_2
    ATTRIBUTES = JPEG2000,fme_basename
    ATTR_ACCUM_MODE = Only Use Result
    COMBINE_GEOM = Use Result
    DATASET = @Value(path_unix)
    FORMAT = JPEG2000
    INTERACT = <No Spatial Filter>
    JPEG2000_GROUP_BY_DATASET = No
    JPEG2000_JPEG2000_EXPOSE_FORMAT_ATTRS = fme_basename,char(50)
    JPEG2000_PREFER_FILE_CS_UNITS = Yes
    JPEG2000_READER_META_ATTRIBUTES = fme_dataset fme_basename
    JPEG2000_READ_OFFSETS_IN_CS_UNITS = No
    JPEG2000_USE_SEARCH_ENVELOPE = NO
    OUTPUT_FEATURES_DISPLAY = Schema and Data Features
    JPEG2000 -> TestFilter_5
TestFilter_5
    DEFAULT_VALUE = <UNFILTERED>
    TEST_LIST = "BOOL_OP,OR,COMPOSITE_TEST,""""""<Unused>"""""",TEST_CLAUSE,CASE_SENSITIVE_TEST @Value(fme_basename) CONTAINS_REGEX B01",B01,"BOOL_OP,OR,COMPOSITE_TEST,""""""<Unused>"""""",TEST_CLAUSE,CASE_SENSITIVE_TEST @Value(fme_basename) CONTAINS_REGEX B02",B02,"BOOL_OP,OR,COMPOSITE_TEST,""""""<Unused>"""""",TEST_CLAUSE,CASE_SENSITIVE_TEST @Value(fme_basename) CONTAINS_REGEX B03",B03,"BOOL_OP,OR,COMPOSITE_TEST,""""""<Unused>"""""",TEST_CLAUSE,CASE_SENSITIVE_TEST @Value(fme_basename) CONTAINS_REGEX B04",B04,"BOOL_OP,OR,COMPOSITE_TEST,""""""<Unused>"""""",TEST_CLAUSE,CASE_SENSITIVE_TEST @Value(fme_basename) CONTAINS_REGEX B05",B05,"BOOL_OP,OR,COMPOSITE_TEST,""""""<Unused>"""""",TEST_CLAUSE,CASE_SENSITIVE_TEST @Value(fme_basename) CONTAINS_REGEX B06",B06,"BOOL_OP,OR,COMPOSITE_TEST,""""""<Unused>"""""",TEST_CLAUSE,CASE_SENSITIVE_TEST @Value(fme_basename) CONTAINS_REGEX B07",B07,"BOOL_OP,OR,COMPOSITE_TEST,""""""<Unused>"""""",TEST_CLAUSE,CASE_SENSITIVE_TEST @Value(fme_basename) CONTAINS_REGEX B08",B08,"BOOL_OP,OR,COMPOSITE_TEST,""""""<Unused>"""""",TEST_CLAUSE,CASE_SENSITIVE_TEST @Value(fme_basename) CONTAINS_REGEX B8A",B8A,"BOOL_OP,OR,COMPOSITE_TEST,""""""<Unused>"""""",TEST_CLAUSE,CASE_SENSITIVE_TEST @Value(fme_basename) CONTAINS_REGEX B09",B09,"BOOL_OP,OR,COMPOSITE_TEST,""""""<Unused>"""""",TEST_CLAUSE,CASE_SENSITIVE_TEST @Value(fme_basename) CONTAINS_REGEX B10",B10,"BOOL_OP,OR,COMPOSITE_TEST,""""""<Unused>"""""",TEST_CLAUSE,CASE_SENSITIVE_TEST @Value(fme_basename) CONTAINS_REGEX B11",B11,"BOOL_OP,OR,COMPOSITE_TEST,""""""<Unused>"""""",TEST_CLAUSE,CASE_SENSITIVE_TEST @Value(fme_basename) CONTAINS_REGEX B12",B12,"BOOL_OP,OR,COMPOSITE_TEST,""""""<Unused>"""""",TEST_CLAUSE,CASE_SENSITIVE_TEST @Value(fme_basename) CONTAINS_REGEX TCI",TCI
    B01 -> Band_1 (output)
    B02 -> Band_2 (output)
    B03 -> Band_3 (output)
    B04 -> Band_4 (output)
    B05 -> Band_5 (output)
    B06 -> Band_6 (output)
    B07 -> Band_7 (output)
    B08 -> Band_8 (output)
    B8A -> Band_8A (output)
    B09 -> Band_9 (output)
    B10 -> Band_10 (output)
    B11 -> Band_11 (output)
    B12 -> Band_12 (output)
    TCI -> TCI (output)
